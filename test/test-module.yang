module test-module {
	namespace "urn:tester:one";
	prefix "tmo";

	organization "";
	contact "";
	description "";
	revision 2015-05-30 {
		description "initial";
		reference "testing";
	}

	container simplecontainer {
		description "";
		leaf simpleleaf {
			type string;
			description "";
		}
	}

	container maincontainer {
		description "";		
		list mainlist {
			key first;

			description "";


			leaf first {
				type string;
				description "";
			}
			leaf second {
				type string;
				description "";
			}
			leaf third {
				type string;
				description "";
			}

			container containerinlist {
				description "";
				leaf deeperleaf {
					type string;
					description "";
				}

				list verydeeplist {
					key akey;
					description "";

					leaf akey {
						type string;
						description "";
					}
				}
			}
		}
	}

	container typetester {
		leaf tint8 {
			type int8;
		}
		leaf tuint8 {
			type uint8;
		}
		leaf tint16 {
			type int16;
		}
		leaf tuint16 {
			type uint16;
		}
		leaf tint32 {
			type int32;
		}
		leaf tuint32 {
			type uint32;
		}
		leaf tint64 {
			type int64;
		}
		leaf tuint64 {
			type uint64;
		}
	}

	container acontainer {
		description "";
		container subcontainer {
			description "";
			leaf deepleaf {
				type uint8;
				description "";
			}
		}
	}

	leaf-list aleaflist {
		type string;
		description "";
	}

	leaf topleaf {
		type string;
	}

}
